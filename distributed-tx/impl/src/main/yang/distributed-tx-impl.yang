module distributed-tx-impl {
    yang-version 1;
    namespace "urn:opendaylight:params:xml:ns:yang:distributed-tx:impl";
    prefix "distributed-tx-impl";

    import config { prefix config; revision-date 2013-04-05; }
    import "distributed-tx-spi" { prefix "distributed-tx-spi"; revision-date 2014-12-10;}
    import "distributed-tx-api" { prefix "distributed-tx-api"; revision-date 2015-01-05;}

    description
        "Service definition for distributed-tx project";

    revision "2014-12-10" {
        description
            "Initial revision";
    }

    identity distributed-tx-impl {
        base config:module-type;
        config:provided-service distributed-tx-api:dtx-provider;
        config:java-name-prefix DistributedTxImpl;
    }

    augment "/config:modules/config:module/config:configuration" {
        case distributed-tx-impl {
            when "/config:modules/config:module/config:type = 'distributed-tx-impl'";
            container tx-provider {
                uses config:service-ref {
                    refine type {
                        mandatory true;
                        config:required-identity distributed-tx-spi:tx-provider;
                    }
                }
            }

            container data-store-tx-provider {
                uses config:service-ref {
                    refine type {
                        mandatory true;
                        config:required-identity distributed-tx-spi:tx-provider;
                    }
                }
            }
        }
    }
}
