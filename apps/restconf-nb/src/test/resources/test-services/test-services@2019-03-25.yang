module test-services {
    yang-version 1.1;
    namespace tests:test-services;
    prefix ts;

    revision "2019-03-25" {
        description
          "Initial revision.";
    }

    container test-data {
        list services {
            key "type-of-service";
            leaf type-of-service {
                type string;
            }

            list instance {
                key "instance-name";

                leaf instance-name {
                    type string;
                }

                leaf provider {
                    type string;
                }
            }

            container next-data {
                leaf next-service {
                    type string;
                }
            }
        }

        leaf-list protocols {
            type string;
        }
    }
}
