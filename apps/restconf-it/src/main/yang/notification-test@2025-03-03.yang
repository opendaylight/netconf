module notification-test {
    yang-version 1.1;
    namespace "test:notification";
    prefix "notif";
    description "Test model for notifications";
    revision "2025-03-03";

    container top {
        leaf id {
            type string;
        }
        notification contNotif {
            leaf msg {
                type string;
            }
        }
    }

    notification example-notification {
        list entry {
            key "id";
            leaf id {
                type string;
            }
            leaf name {
                type string;
            }
            leaf value {
                type string;
            }
        }
    }
}
