module example-action {
    yang-version 1.1;
    namespace "example:action";
    prefix "ea";
    revision "2024-09-19";

    container root {
        action example-action {
            input {
                leaf data {
                    type string;
                }
            }
            output {
                leaf response {
                    type string;
                }
            }
        }

        action not-implemented {
            input {
                leaf data {
                    type string;
                }
            }
            output {
                leaf response {
                    type string;
                }
            }
        }
    }
}
