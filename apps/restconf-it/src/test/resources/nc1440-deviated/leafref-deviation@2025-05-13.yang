module leafref-deviation {
  yang-version 1.1;
  namespace "leafref:deviation";
  prefix dev;
  revision "2025-05-13";

  import leafref-source {
    prefix src;
  }

  deviation "/src:conts" {
    deviate not-supported;
    description
      "Deviate container that defined in leafref-source model.";
  }
}
