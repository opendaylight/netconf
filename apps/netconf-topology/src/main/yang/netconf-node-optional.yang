module netconf-node-optional {
    namespace "urn:opendaylight:netconf-node-optional";
    prefix "netnopt";

    import network-topology { prefix nt; revision-date 2013-10-21; }
    import odl-codegen-extensions { prefix oce; }

    revision 2022-12-25 {
        description "Datastore locking moved to odl-netconf-device.";
    }

    revision "2019-06-14" {
        description "Initial revision of Node Optional model";
    }

    grouping netconf-node-augmented-optional-fields {
        container ignore-missing-schema-sources {
            description "Allows mount point to reconnect on the 'missing schema sources' error.
                WARNING - enabling the reconnection on the 'missing schema sources' error can lead
                to unexpected errors at runtime.";
            leaf allowed {
                type boolean;
                default false;
                description "Allows reconnection of the mount point. Default false.";
            }
            leaf reconnect-time {
                type uint32;
                default 5000;
                description "Time for reconnection - in units milliseconds. Default 5000 ms.";
            }
        }
    }

    augment "/nt:network-topology/nt:topology/nt:node" {
        when "../../nt:topology-types/topology-netconf";
        oce:augment-identifier "netconf-node-augmented-optional";
        uses netconf-node-augmented-optional-fields;
    }
}
