module odl-device-notification {
  namespace "urn:opendaylight:device:notification";
  prefix "device-notifi";

  import ietf-inet-types {
    prefix inet;
  }

  organization "OpenDaylight";
  contact "Nikhil Soni <nikk.sonitech@gmail.com>";

  description
    "This module contains the definition of methods related to
    device notification model

     Copyright (c)2022 Nikhil Soni and others. All rights reserved.

     This program and the accompanying materials are made available
     under the terms of the Eclipse Public License v1.0 which
     accompanies this distribution, and is available at
     http://www.eclipse.org/legal/epl-v10.html";

  revision "2024-02-18" {
    description "Corrected output to result in a stream name";
  }

  revision "2022-11-06" {
    description
      "Initial revision";
  }

  rpc subscribe-device-notification {
    description
      "Subscribe to notifications on specified device.";

    input {
      leaf path {
        type instance-identifier;
        description "Device mount point path";
      }
    }
    output {
      leaf stream-name {
        type string;
        description "Notification stream name.";
      }
    }
  }
}
