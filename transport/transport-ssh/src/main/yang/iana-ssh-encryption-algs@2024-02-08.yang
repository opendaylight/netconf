module iana-ssh-encryption-algs {
  yang-version 1.1;
  namespace "urn:ietf:params:xml:ns:yang:iana-ssh-encryption-algs";
  prefix sshea;

  organization
    "Internet Assigned Numbers Authority (IANA)";

  contact
    "Postal: ICANN
             12025 Waterfront Drive, Suite 300
             Los Angeles, CA  90094-2536
             United States of America
     Tel:    +1 310 301 5800
     Email:  iana@iana.org";

  description
    "This module defines identities for the encryption algorithms
     defined in the 'Encryption Algorithm Names' sub-registry of the
     'Secure Shell (SSH) Protocol Parameters' registry maintained
     by IANA.

     Copyright (c) 2024 IETF Trust and the persons identified as
     authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     The initial version of this YANG module is part of RFC EEEE
     (https://www.rfc-editor.org/info/rfcEEEE); see the RFC
     itself for full legal notices.";

  revision 2024-02-08 {
    description
      "Reflects contents of the encryption algorithms registry.";
    reference
      "RFC EEEE: YANG Groupings for SSH Clients and SSH Servers";
  }

  // Typedefs

  typedef encryption-algorithm-ref {
    type identityref {
      base "encryption-alg-base";
    }
    description
      "A reference to an SSH encryption algorithm identifier.";
  }


  // Identities

  identity encryption-alg-base {
    description
      "Base identity for SSH encryption algorithms.";
  }

  identity triple-des-cbc {
    base encryption-alg-base;
    description
      "Identity for the '3des-cbc' algorithm.  Section 6.3";
    reference
      "RFC 4253:
         The Secure Shell (SSH) Transport Layer Protocol";
  }

  identity blowfish-cbc {
    base encryption-alg-base;
    description
      "Identity for the 'blowfish-cbc' algorithm.  Section 6.3";
    reference
      "RFC 4253:
         The Secure Shell (SSH) Transport Layer Protocol";
  }

  identity twofish256-cbc {
    base encryption-alg-base;
    description
      "Identity for the 'twofish256-cbc' algorithm.  Section 6.3";
    reference
      "RFC 4253:
         The Secure Shell (SSH) Transport Layer Protocol";
  }

  identity twofish-cbc {
    base encryption-alg-base;
    description
      "Identity for the 'twofish-cbc' algorithm.  Section 6.3";
    reference
      "RFC 4253:
         The Secure Shell (SSH) Transport Layer Protocol";
  }

  identity twofish192-cbc {
    base encryption-alg-base;
    description
      "Identity for the 'twofish192-cbc' algorithm.  Section 6.3";
    reference
      "RFC 4253:
         The Secure Shell (SSH) Transport Layer Protocol";
  }

  identity twofish128-cbc {
    base encryption-alg-base;
    description
      "Identity for the 'twofish128-cbc' algorithm.  Section 6.3";
    reference
      "RFC 4253:
         The Secure Shell (SSH) Transport Layer Protocol";
  }

  identity aes256-cbc {
    base encryption-alg-base;
    description
      "Identity for the 'aes256-cbc' algorithm.  Section 6.3";
    reference
      "RFC 4253:
         The Secure Shell (SSH) Transport Layer Protocol";
  }

  identity aes192-cbc {
    base encryption-alg-base;
    description
      "Identity for the 'aes192-cbc' algorithm.  Section 6.3";
    reference
      "RFC 4253:
         The Secure Shell (SSH) Transport Layer Protocol";
  }

  identity aes128-cbc {
    base encryption-alg-base;
    description
      "Identity for the 'aes128-cbc' algorithm.  Section 6.3";
    reference
      "RFC 4253:
         The Secure Shell (SSH) Transport Layer Protocol";
  }

  identity serpent256-cbc {
    base encryption-alg-base;
    description
      "Identity for the 'serpent256-cbc' algorithm.  Section 6.3";
    reference
      "RFC 4253:
         The Secure Shell (SSH) Transport Layer Protocol";
  }

  identity serpent192-cbc {
    base encryption-alg-base;
    description
      "Identity for the 'serpent192-cbc' algorithm.  Section 6.3";
    reference
      "RFC 4253:
         The Secure Shell (SSH) Transport Layer Protocol";
  }

  identity serpent128-cbc {
    base encryption-alg-base;
    description
      "Identity for the 'serpent128-cbc' algorithm.  Section 6.3";
    reference
      "RFC 4253:
         The Secure Shell (SSH) Transport Layer Protocol";
  }

  identity arcfour {
    base encryption-alg-base;
    status obsolete;
    description
      "Identity for the 'arcfour' algorithm.";
    reference
      "RFC 8758:
         Deprecating RC4 in Secure Shell (SSH)";
  }

  identity idea-cbc {
    base encryption-alg-base;
    description
      "Identity for the 'idea-cbc' algorithm.  Section 6.3";
    reference
      "RFC 4253:
         The Secure Shell (SSH) Transport Layer Protocol";
  }

  identity cast128-cbc {
    base encryption-alg-base;
    description
      "Identity for the 'cast128-cbc' algorithm.  Section 6.3";
    reference
      "RFC 4253:
         The Secure Shell (SSH) Transport Layer Protocol";
  }

  identity none {
    base encryption-alg-base;
    description
      "Identity for the 'none' algorithm.  Section 6.3";
    reference
      "RFC 4253:
         The Secure Shell (SSH) Transport Layer Protocol";
  }

  identity des-cbc {
    base encryption-alg-base;
    status obsolete;
    description
      "Identity for the 'des-cbc' algorithm.";
    reference
      "FIPS-46-3:
         Data Encryption Standard (DES)";
  }

  identity arcfour128 {
    base encryption-alg-base;
    status obsolete;
    description
      "Identity for the 'arcfour128' algorithm.";
    reference
      "RFC 8758:
         Deprecating RC4 in Secure Shell (SSH)";
  }

  identity arcfour256 {
    base encryption-alg-base;
    status obsolete;
    description
      "Identity for the 'arcfour256' algorithm.";
    reference
      "RFC 8758:
         Deprecating RC4 in Secure Shell (SSH)";
  }

  identity aes128-ctr {
    base encryption-alg-base;
    description
      "Identity for the 'aes128-ctr' algorithm.";
    reference
      "RFC 4344:
         The Secure Shell (SSH) Transport Layer Encryption Modes";
  }

  identity aes192-ctr {
    base encryption-alg-base;
    description
      "Identity for the 'aes192-ctr' algorithm.";
    reference
      "RFC 4344:
         The Secure Shell (SSH) Transport Layer Encryption Modes";
  }

  identity aes256-ctr {
    base encryption-alg-base;
    description
      "Identity for the 'aes256-ctr' algorithm.";
    reference
      "RFC 4344:
         The Secure Shell (SSH) Transport Layer Encryption Modes";
  }

  identity triple-des-ctr {
    base encryption-alg-base;
    description
      "Identity for the '3des-ctr' algorithm.";
    reference
      "RFC 4344:
         The Secure Shell (SSH) Transport Layer Encryption Modes";
  }

  identity blowfish-ctr {
    base encryption-alg-base;
    description
      "Identity for the 'blowfish-ctr' algorithm.";
    reference
      "RFC 4344:
         The Secure Shell (SSH) Transport Layer Encryption Modes";
  }

  identity twofish128-ctr {
    base encryption-alg-base;
    description
      "Identity for the 'twofish128-ctr' algorithm.";
    reference
      "RFC 4344:
         The Secure Shell (SSH) Transport Layer Encryption Modes";
  }

  identity twofish192-ctr {
    base encryption-alg-base;
    description
      "Identity for the 'twofish192-ctr' algorithm.";
    reference
      "RFC 4344:
         The Secure Shell (SSH) Transport Layer Encryption Modes";
  }

  identity twofish256-ctr {
    base encryption-alg-base;
    description
      "Identity for the 'twofish256-ctr' algorithm.";
    reference
      "RFC 4344:
         The Secure Shell (SSH) Transport Layer Encryption Modes";
  }

  identity serpent128-ctr {
    base encryption-alg-base;
    description
      "Identity for the 'serpent128-ctr' algorithm.";
    reference
      "RFC 4344:
         The Secure Shell (SSH) Transport Layer Encryption Modes";
  }

  identity serpent192-ctr {
    base encryption-alg-base;
    description
      "Identity for the 'serpent192-ctr' algorithm.";
    reference
      "RFC 4344:
         The Secure Shell (SSH) Transport Layer Encryption Modes";
  }

  identity serpent256-ctr {
    base encryption-alg-base;
    description
      "Identity for the 'serpent256-ctr' algorithm.";
    reference
      "RFC 4344:
         The Secure Shell (SSH) Transport Layer Encryption Modes";
  }

  identity idea-ctr {
    base encryption-alg-base;
    description
      "Identity for the 'idea-ctr' algorithm.";
    reference
      "RFC 4344:
         The Secure Shell (SSH) Transport Layer Encryption Modes";
  }

  identity cast128-ctr {
    base encryption-alg-base;
    description
      "Identity for the 'cast128-ctr' algorithm.";
    reference
      "RFC 4344:
         The Secure Shell (SSH) Transport Layer Encryption Modes";
  }

  identity AEAD_AES_128_GCM {
    base encryption-alg-base;
    description
      "Identity for the 'AEAD_AES_128_GCM' algorithm.  Section 6.1";
    reference
      "RFC 5647:
         AES Galois Counter Mode for the Secure Shell Transport Layer
         Protocol";
  }

  identity AEAD_AES_256_GCM {
    base encryption-alg-base;
    description
      "Identity for the 'AEAD_AES_256_GCM' algorithm.  Section 6.2";
    reference
      "RFC 5647:
         AES Galois Counter Mode for the Secure Shell Transport Layer
         Protocol";
  }

}
