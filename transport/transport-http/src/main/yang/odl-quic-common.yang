module odl-quic-common {
  yang-version 1.1;
  namespace "urn:opendaylight:yang:quic:common";
  prefix "oqc";

  description
    "OpenDaylight configuration model for QUIC transport.

     Copyright (c) 2026 PANTHEON.tech, s.r.o. and others.  All rights reserved.

     This program and the accompanying materials are made available under the
     terms of the Eclipse Public License v1.0 which accompanies this distribution,
     and is available at http://www.eclipse.org/legal/epl-v10.html";

  revision "2026-09-01" {
    description
      "Add 'max-idle-timeout' to 'transport-params-grouping', so it can be
       set on both quic-client-parameters and quic-server-parameters.";
  }

  revision "2026-04-15" {
    description "Initial revision";
  }

  typedef varint {
    type uint64 {
      range "0..4611686018427387903";
    }
    description
      "A QUIC transport parameter value encoded as a variable- length integer.

       The largest value allowed by QUIC variable-length integer encoding is
       2^62 - 1.";
    reference
      "RFC 9000: QUIC: A UDP-Based Multiplexed and Secure Transport,
       Section 16";
  }

  grouping transport-params-grouping {
    description
      "A reusable grouping for QUIC transport parameters.";

    leaf initial-max-data {
      type varint;
      default "4194304";
      description
        "The QUIC initial_max_data transport parameter used to limit
         connection-level flow control.";
      reference
        "RFC 9000: QUIC: A UDP-Based Multiplexed and Secure Transport,
         Section 18.2";
    }

    leaf initial-max-stream-data-bidi-remote {
      type varint;
      default "262144";
      description
        "The QUIC initial_max_stream_data_bidi_remote transport parameter used
         to limit flow control for remotely initiated bidirectional streams.";
      reference
        "RFC 9000: QUIC: A UDP-Based Multiplexed and Secure Transport,
         Section 18.2";
    }

    leaf initial-max-streams-bidi {
      type uint32;
      default "100";
      description
        "The QUIC initial_max_streams_bidi transport parameter used to limit
         the number of bidirectional streams.";
      reference
        "RFC 9000: QUIC: A UDP-Based Multiplexed and Secure Transport,
         Sections 4.6 and 18.2";
    }

    leaf max-idle-timeout {
      type varint;
      units "milliseconds";
      default "30000";
      description
        "The QUIC max_idle_timeout transport parameter. A connection that
         remains idle for longer than this is silently closed and its state
         discarded by the endpoint enforcing it, even if the peer never sends
         a CONNECTION_CLOSE frame, e.g. because it crashed or a middlebox
         dropped the path. This is the only liveness check a QUIC endpoint
         gets, since QUIC runs over UDP and so has no equivalent of TCP's
         SO_KEEPALIVE. A value of zero disables the check.

         A server-sent event stream is otherwise silent at the QUIC layer:
         only the server's periodic SSE heartbeat ('ping') traffic keeps such
         a connection from looking idle. For a quiet subscription to survive
         this timeout, the heartbeat interval must stay well under it and
         must not itself be disabled; otherwise a healthy but quiet
         subscription is silently torn down once this timeout elapses.";
      reference
        "RFC 9000: QUIC: A UDP-Based Multiplexed and Secure Transport,
         Sections 10.1 and 18.2";
    }
  }
}
