module sal-remote-augment {

    yang-version 1;
    namespace "urn:sal:restconf:event:subscription";
    prefix "salrmt-aug-ev-subscr";

    import sal-remote {prefix salrmt; revision-date "2014-01-14";}

    description
        "Added input parameters to rpc create-data-change-event-subscription and to create-notification-stream";

    revision "2014-07-08" {
    }

    augment "/salrmt:create-data-change-event-subscription/salrmt:input" {
        leaf datastore {
            type enumeration {
                enum OPERATIONAL;
                enum CONFIGURATION;
            }
        }
        leaf scope {
            type enumeration {
                enum BASE;
                enum ONE;
                enum SUBTREE;
            }
        }
    }

    augment "/salrmt:create-notification-stream/salrmt:input" {
        leaf notification-output-type {
            type enumeration {
                enum JSON;
                enum XML;
            }
            default "XML";
            description "Input parameter which type of output will be parsed on notification";
        }
    }

}
