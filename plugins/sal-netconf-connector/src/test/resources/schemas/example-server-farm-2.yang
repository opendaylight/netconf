module example-server-farm-2 {
  yang-version 1.1;
  namespace "urn:example:server-farm-2";
  prefix "sfarm2";
  revision 2019-05-20;

  import example-server-farm { prefix sfarm; revision-date 2018-08-07; }

  augment "/sfarm:server" {
    container applications {
      list application {
        key "name";
        leaf name {
          type string;
        }

        action kill {
        }
      }
    }
  }
}
