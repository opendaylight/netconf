module config {
    yang-version 1;
    namespace "urn:opendaylight:mdsal:mapping:test";
    prefix "map";

    revision "2015-02-26";

    identity foo {
            description "dummy identity";
    }
    container mapping-nodes {

        list multiple-keys {
            key "key3 key1 key2";

            leaf value1 {
                type string;
            }

            leaf key1 {
                type string;
            }

            leaf value2 {
                type string;
            }

            leaf key2 {
                type string;
            }

            leaf key3 {
                type string;
            }
        }
        
        list mapping-node {
            key "id";
            leaf id {
                type string;
            }

            leaf content {
                type string;
            }

            choice ordered-choice {
                case a {
                    container ordered-items {
                        list ordered-item {
                            key "id";
                            ordered-by user;
                            leaf id {
                                type string;
                            }

                            leaf content {
                                type string;
                            }
                        }
                    }
                }
                case b {
                    container augmented-ordered-items {

                    }
                }
            }
        }
    }

    augment "/map:mapping-nodes/map:mapping-node/map:ordered-choice/map:b/map:augmented-ordered-items" {
        list augmented-ordered-item {
            key "id";
            ordered-by user;
            leaf id {
                type string;
            }

            leaf content {
                type string;
            }
        }
    }

    container top {

        container users {

            list user {

                key "name";

                leaf name {
                    type string;
                }

                leaf type {
                    type string;
                }

                leaf full-name {
                    type string;
                }

                container company-info {

                    leaf dept {
                        type string;
                    }

                    leaf id {
                        type string;
                    }
                }
            }
        }

        container modules {

            list module {

                key "id";

                leaf id {
                    type string;
                }

                leaf type {
                    type string;
                }

                leaf desc {
                    type string;
                }
            }
        }

        choice choice-node {
            case a {
                leaf text {
                    type string;
                }
            }

            case b {
                container text-cont {
                    leaf text {
                        type string;
                    }
                }
            }
        }

    } //top

    augment "/map:top/map:choice-node" {
        case c {
            leaf augmented-case {
                type string;
            }
        }

        case d {
            container choice-wrapper {
                choice inner-choice {
                    case ia {
                        leaf text {
                            type string;
                        }
                    }

                    case ib {
                        leaf text2 {
                            type string;
                        }
                    }
                }
            }
        }
    }

    augment "/map:top/map:modules" {
        container augmented-container {
            leaf identifier {
                type string;
            }
        }
    }

    augment "/map:top/map:modules" {
        leaf leaf-from-augment {
            type string;
        }
    }

    augment "/map:top" {
        container mid-level {
            container low-level {
                container lowest-level {
                    leaf-list note {
                        type string;
                    }
                }
            }
            container low-level2 {
                leaf-list note {
                    type string;
                }
            }
        }
    }

    list toplevel-list {
        key "id";
        leaf id {
            type string;
        }

        leaf content {
            type string;
        }
    }

    container top-with-presence {
        presence "For testing presence containers";

    }
}
