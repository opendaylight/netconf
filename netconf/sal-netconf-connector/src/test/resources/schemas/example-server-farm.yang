module example-server-farm {
  yang-version 1.1;
  namespace "urn:example:server-farm";
  prefix "sfarm";
  revision 2018-08-07;

  list server {
    key name;
    leaf name {
      type string;
    }
    action reset {
      input {
        leaf reset-at {
          type string;
          mandatory true;
        }
      }
      output {
        leaf reset-finished-at {
          type string;
          mandatory true;
        }
      }
    }
  }

  container device {
    action start {
      input {
        leaf start-at {
          type string;
          mandatory true;
        }
      }
      output {
        leaf start-finished-at {
          type string;
          mandatory true;
        }
      }
    }
  }

  container box-out {
    container box-in {
      action open {
      }
    }
  }
}
