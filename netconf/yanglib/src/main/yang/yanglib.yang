module yanglib {
    yang-version 1;
    namespace "urn:opendaylight:params:xml:ns:yang:controller:yanglib:impl";
    prefix "yanglib";

    description
        "Service configuration for yanglib project";

    revision "2014-12-10" {
        description
            "Initial revision";
    }

    container yanglib-config {
        // TODO extracting the schema repositories
        leaf cache-folder {
            mandatory true;
            type string;
            default "cache/schema";
            description "local filesystem folder to use as cache + to load yang models from";
        }

        // TODO it would be better if the binding arguments could be located by the app automatically
        leaf binding-addr {
            mandatory true;
            type string;
            default "localhost";
            // TODO make this uri
            description "binding address is necessary for generating proper URLS (accessible from the outside world)
                         for models present directly in the library";
        }

        leaf binding-port {
            mandatory true;
            type uint32;
            default 5000;
            // TODO proper type
            description "binding port is necessary for generating proper URLS (accessible from the outside world)
                         for models present directly in the library";
        }
    }
}
