module netconf-clustered-topology-config {
    yang-version 1;
    namespace "urn:opendaylight:netconf:topology:singleton:config";
    prefix nctc;

    description
      "Configuration for Netconf Clustered Topology";

    revision "2017-04-19" {
        description
            "Initial revision.";
    }

    container config {
        leaf write-transaction-idle-timeout {
            type uint16;
            default 0;
            description "Idle time in seconds after which write transaction is cancelled automatically.
            If 0, automatic cancellation is turned off.";
        }
    }
}
