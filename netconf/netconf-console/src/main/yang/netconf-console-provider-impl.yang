module netconf-console-provider-impl {
    namespace "urn:opendaylight:netconf:console:provider:impl";
    prefix "netconf-console-provider-impl";

    import config { prefix config; revision-date 2013-04-05; }
    import opendaylight-md-sal-binding { prefix mdsal; revision-date 2013-10-28; }

    revision 2016-03-23 {
        description "Initial revision";
    }

    identity netconf-console-provider-impl {
        base config:module-type;
        config:java-name-prefix NetconfConsoleProvider;
    }

    augment "/config:modules/config:module/config:configuration" {
        case netconf-console-provider-impl {
            when "/config:modules/config:module/config:type = 'netconf-console-provider-impl'";
            container broker {
                uses config:service-ref {
                    refine type {
                        mandatory true;
                        config:required-identity mdsal:binding-broker-osgi-registry;
                    }
                }
            }
        }
    }
}
