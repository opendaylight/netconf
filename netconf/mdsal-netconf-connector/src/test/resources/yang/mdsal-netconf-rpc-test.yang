module rpc-test {
    yang-version 1;
    namespace "urn:opendaylight:mdsal:mapping:rpc:test";
    prefix "rpc";

    revision "2015-04-08";

    rpc void-input-output-rpc {

    }

    rpc void-output-rpc {
        input {
            leaf test-string {
                type string;
            }

            leaf test-string2 {
                type string;
            }
        }
    }

    rpc nonvoid-rpc {
        input {
            leaf test-string {
                type string;
            }

            leaf test-string2 {
                type string;
            }
        }

        output {
            leaf test-string {
                type string;
            }

            leaf test-string2 {
                type string;
            }
        }
    }

    rpc container-rpc {
        input {
            container cont1 {
                leaf test-string {
                    type string;
                }

                leaf test-string2 {
                    type string;
                }
            }

            container cont2 {
                leaf test-string {
                    type string;
                }

                leaf test-string2 {
                    type string;
                }
            }
        }

        output {
            container cont1 {
                leaf test-string {
                    type string;
                }

                leaf test-string2 {
                    type string;
                }
            }

            container cont2 {
                leaf test-string {
                    type string;
                }

                leaf test-string2 {
                    type string;
                }
            }
        }
    }
}
