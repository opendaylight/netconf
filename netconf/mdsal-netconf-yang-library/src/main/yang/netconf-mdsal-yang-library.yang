module netconf-mdsal-yang-library {
    yang-version 1;
    namespace "urn:opendaylight:params:xml:ns:yang:controller:netconf:mdsal:yang:library";
    prefix "nmyanglib";

    import opendaylight-md-sal-dom { prefix md-sal-dom; revision-date 2013-10-28; }
    import opendaylight-md-sal-binding {prefix md-sal-binding; revision-date 2013-10-28;}
    import config { prefix config; revision-date 2013-04-05; }

    organization "Cisco Systems, Inc.";

    description
        "This module contains the base YANG definitions for
         MDSAL netconf yang module library implementation";

    revision "2016-06-17" {
        description
            "Initial revision.";
    }

    identity netconf-mdsal-yanglib {
        base config:module-type;
    }

    augment "/config:modules/config:module/config:configuration" {
        case netconf-mdsal-yanglib {
            when "/config:modules/config:module/config:type = 'netconf-mdsal-yanglib'";

            container root-schema-service {
                uses config:service-ref {
                    refine type {
                        mandatory false;
                        config:required-identity md-sal-dom:schema-service;
                    }
                }
            }

            container binding-aware-broker {
                uses config:service-ref {
                    refine type {
                        mandatory true;
                        config:required-identity md-sal-binding:binding-broker-osgi-registry;
                    }
                }
            }
        }
    }
}
