module callhome-status{
    namespace "urn:opendaylight:callhome:device-status";
    prefix "callhome-status";

    import odl-netconf-callhome-server { prefix callhome; revision-date "2020-10-15"; }

    revision 2017-01-12 {
        description "Initial revision";
    }

    augment "/callhome:netconf-callhome-server/callhome:allowed-devices/callhome:device"{
        leaf device-status {
          config false;
          type enumeration {
              enum CONNECTED;
              enum FAILED_AUTH_FAILURE;
              enum FAILED_NOT_ALLOWED;
              enum FAILED;
              enum DISCONNECTED;
          }
          default DISCONNECTED;
        }
    }
}
