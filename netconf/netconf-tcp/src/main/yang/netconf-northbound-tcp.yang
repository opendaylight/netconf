module netconf-northbound-tcp {
    yang-version 1;
    namespace "urn:opendaylight:params:xml:ns:yang:controller:netconf:northbound:tcp";
    prefix "nni";

    import netconf-northbound-mapper { prefix nnm; revision-date 2015-01-14; }
    import netconf-northbound { prefix nn; revision-date 2015-01-14; }
    import config { prefix config; revision-date 2013-04-05; }
    import threadpool {prefix th;}
    import netty {prefix netty;}
    import ietf-inet-types { prefix inet; revision-date 2013-07-15; }

    organization "Cisco Systems, Inc.";

    description
        "This module contains the base YANG definitions for
         a default implementation of netconf northbound tcp server";

    revision "2015-04-23" {
        description
            "Initial revision.";
    }

    identity netconf-northbound-tcp {
        base config:module-type;
        config:java-name-prefix NetconfNorthboundTcp;
        status deprecated;
    }

    augment "/config:modules/config:module/config:configuration" {
        case netconf-northbound-tcp {
            when "/config:modules/config:module/config:type = 'netconf-northbound-tcp'";

            status deprecated;

            leaf port {
                type inet:port-number;
                default 2831;
            }

            leaf binding-address {
                type inet:ip-address;
                default "0.0.0.0";
            }

            container dispatcher {
                uses config:service-ref {
                    refine type {
                        config:required-identity nn:netconf-server-dispatcher;
                    }
                }
            }
        }
    }

}
