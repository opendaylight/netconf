module aaa-authn-netconf-plugin {

    yang-version 1;
    namespace "config:aaa:authn:netconf:plugin";
    prefix "aaa-authn-store-cfg";

    import config { prefix config; revision-date 2013-04-05; }
    import netconf-auth { prefix na; revision-date 2015-07-15; }

    revision "2015-07-15" {
        description
            "Initial revision.";
    }

    identity aaa-authn-netconf-plugin {
            base config:module-type;
            config:java-name-prefix AuthProvider;
            config:provided-service na:netconf-auth-provider;
            status deprecated;
    }

    augment "/config:modules/config:module/config:configuration" {
        status deprecated;
        case aaa-authn-netconf-plugin {
            when "/config:modules/config:module/config:type = 'aaa-authn-netconf-plugin'";
            // no config yet
       }
    }
}
