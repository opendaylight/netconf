module netconf-node-topology {
    namespace "urn:opendaylight:netconf-node-topology";
    prefix "nettop";

    import network-topology { prefix nt; revision-date 2013-10-21; }
    import yang-ext { prefix ext; revision-date "2013-07-09";}
    import netconf-node-optional { prefix nno; }
    import odl-netconf-device { prefix ond; }

    revision 2022-12-25 {
        description "Refactored into odl-netconf-device";
    }

    revision "2015-01-14" {
        description "Initial revision of Topology model";
    }

    grouping netconf-node-fields {
      uses ond:credentials;
      uses ond:connection-parameters;
      uses ond:netconf-schema-storage;
      uses ond:datastore-access;
    }

    rpc create-device {
        input {
            uses netconf-node-fields;
            uses nno:netconf-node-augmented-optional-fields;
            leaf node-id {
                type string;
            }
        }
    }

    rpc delete-device {
        input {
            leaf node-id {
                type string;
            }
        }
    }

    augment "/nt:network-topology/nt:topology/nt:topology-types" {
        container topology-netconf {
            presence "The presence of the container node indicates a network
                      of NETCONF devices";
        }
    }

    augment "/nt:network-topology/nt:topology/nt:node" {
        when "../../nt:topology-types/topology-netconf";
        ext:augment-identifier "netconf-node";

        uses netconf-node-fields;
        uses ond:connection-oper;
        uses nno:netconf-node-augmented-optional-fields;
        ext:mount;
    }
}
