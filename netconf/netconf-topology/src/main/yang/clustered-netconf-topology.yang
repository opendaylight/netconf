module clustered-netconf-topology {

    yang-version 1;
    namespace "urn:opendaylight:params:xml:ns:yang:controller:clustered:netconf:topology";
    prefix "nt";

    import config { prefix config; revision-date 2013-04-05; }
    import threadpool {prefix th;}
    import netty {prefix netty;}
    import opendaylight-md-sal-dom {prefix dom;}
    import opendaylight-md-sal-binding {prefix md-sal-binding; revision-date 2013-10-28;}
    import odl-netconf-cfg { prefix cfg-net; revision-date 2014-04-08; }
    import shared-schema-repository { prefix sh; revision-date 2015-07-27; }
    import netconf-topology { prefix topo; revision-date 2015-07-27; }
    import opendaylight-entity-ownership-service { prefix eos; revision-date 2015-08-10; }
    import actor-system-provider-service { prefix asp; revision-date 2015-10-05; }

    description
            "Module definition for Netconf topolgy. Netconf topology provides a set of common configuration ";

    revision "2015-11-04" {
        description
            "Initial revision";
    }

    identity clustered-netconf-topology-impl {
        base config:module-type;
        config:java-name-prefix ClusteredNetconfTopology;
        config:provided-service topo:netconf-topology;
    }

    augment "/config:modules/config:module/config:configuration" {
        case clustered-netconf-topology-impl {
            when "/config:modules/config:module/config:type = 'clustered-netconf-topology-impl'";

            leaf topology-id {
                mandatory true;
                type string;
            }

            leaf concurrent-rpc-limit {
                type uint16 {
                    range "1..max";
                }
                mandatory true;
                description "limit of concurrent messages that can be send before reply messages are received";
            }

            container dom-registry {
                uses config:service-ref {
                    refine type {
                        mandatory true;
                        config:required-identity dom:dom-broker-osgi-registry;
                    }
                }
            }

            container binding-registry {
                uses config:service-ref {
                    refine type {
                        mandatory true;
                        config:required-identity md-sal-binding:binding-broker-osgi-registry;
                    }
                }
            }

            container event-executor {
                uses config:service-ref {
                    refine type {
                        mandatory true;
                        config:required-identity netty:netty-event-executor;
                    }
                }
            }

            container processing-executor {
                uses config:service-ref {
                    refine type {
                        mandatory true;
                        config:required-identity th:threadpool;
                    }
                }

                description "Makes up for flaws in netty threading design";
            }

            container client-dispatcher {
                uses config:service-ref {
                    refine type {
                        mandatory false;
                        config:required-identity cfg-net:netconf-client-dispatcher;
                    }
                }
            }

            container keepalive-executor {
                uses config:service-ref {
                    refine type {
                        mandatory false;
                        config:required-identity th:scheduled-threadpool;
                    }
                }

                description "Dedicated solely to keepalive execution";
            }

            container shared-schema-repository {
                uses config:service-ref {
                    refine type {
                        mandatory true;
                        config:required-identity sh:shared-schema-repository;
                    }
                }
            }

            container entity-ownership-service {
                uses config:service-ref {
                    refine type {
                        mandatory true;
                        config:required-identity eos:entity-ownership-service;
                    }
                }
            }

            container actor-system-provider-service {
                uses config:service-ref {
                    refine type {
                        mandatory true;
                        config:required-identity asp:actor-system-provider-service;
                    }
                }
            }
        }
    }
}
