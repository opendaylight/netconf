module network-topology-network-topology-augment-test  {
  namespace "urn:TBD:params:xml:ns:yang:network-topology-augment-test";
  prefix "ntat";

  import network-topology {
    prefix "nt";
    revision-date 2013-10-21;
  }

  description "This module defines test model for the topology of a network with augmented node";
  revision 2016-08-08;

  augment /nt:network-topology/nt:topology/nt:node {
    leaf test-id {
      type uint16;
    }
    leaf test-name {
      type string;
    }
  }
}
