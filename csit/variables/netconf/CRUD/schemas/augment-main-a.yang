module augment-main-a {
  yang-version 1.1;
  namespace "ns:augment:main:a";
  prefix "aumaa";

  import main {prefix mn; revision-date 2014-01-21;}

  revision "2014-01-21" {}

  augment "/mn:cont" {
    container cont1 {
      leaf lf11 {
      	type string;
      }

      action reset {
       description "Reset an interface.";
        input {
          leaf delay {
            type uint32;
            units "seconds";
            default "0";
            description "Number of seconds to wait before starting the interface reset.";
          }
        }
      }
    }
  }
}
