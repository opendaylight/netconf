module ietf-netconf-monitoring-extension {

    yang-version 1;

    namespace
      "urn:ietf:params:xml:ns:yang:ietf-netconf-monitoring-extension";

    prefix ncme;

    import ietf-netconf-monitoring {
      prefix ncm;
    }

    revision "2013-12-10" {
      description "Initial revision.";

    }

    identity netconf-tcp {
      base ncm:transport;
      description
        "NETCONF over TCP.";
    }

    augment "/ncm:netconf-state/ncm:sessions/ncm:session" {
      leaf session-identifier {
        type string;
      }
    }

}
