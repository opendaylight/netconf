module regex1 {
    namespace "urn:regex1";
    prefix "re1";
    revision 2024-09-12 {
        description "Initial revision.";
    }

    container cntr {
        leaf lf {
            type string {
                length "1..100";
                pattern "[A-Z]*[0-9]";
            }
        }
    }
}
