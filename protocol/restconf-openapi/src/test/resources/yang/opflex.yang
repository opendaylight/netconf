module opflex {
    yang-version 1;

    namespace "urn:opendaylight:groupbasedpolicy:opflex";
    prefix "opflex";





    description
        "This module defines the group-based policy OpFlex renderer model.";

    revision "2014-05-28" {
        description
            "Initial revision.";
    }

    typedef serialization {
        description
            "The serialization to use for OpFlex messages.";

        type enumeration {
            enum json {
                description
                "JSON 1.0 serialization.";
            }
            enum xml {
                description
                "XML serialization.";
            }
            enum binary {
                description
                "OpFlex binary serialization.";
            }
        }
    }

    // ******************
    // Configuration Data
    // ******************
    leaf domain {
        description
            "The OpFlex administrative domain.";

        config true;

        type string;
    }
}
