module ietf-restconf-client {
  yang-version 1.1;
  namespace "urn:ietf:params:xml:ns:yang:ietf-restconf-client";
  prefix rcc;

  import ietf-yang-types {
    prefix yang;
    reference
      "RFC 6991: Common YANG Data Types";
  }

  import ietf-tcp-server {
    prefix tcps;
    reference
      "RFC DDDD: YANG Groupings for TCP Clients and TCP Servers";
  }

  import ietf-http-client {
    prefix httpc;
    reference
      "RFC GGGG: YANG Groupings for HTTP Clients and HTTP Servers";
  }

  organization
    "IETF NETCONF (Network Configuration) Working Group";

  contact
    "WG Web:   https://datatracker.ietf.org/wg/netconf
     WG List:  NETCONF WG list <mailto:netconf@ietf.org>
     Author:   Kent Watsen <mailto:kent+ietf@watsen.net>";

  description
    "This module contains a collection of YANG definitions
     for configuring RESTCONF clients.

     Copyright (c) 2024 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC IIII
     (https://www.rfc-editor.org/info/rfcIIII); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2024-08-14 {
    description
      "Initial version";
    reference
      "RFC IIII: RESTCONF Client and Server Models";
  }

  // Features

  feature https-initiate {
    description
      "The 'https-initiate' feature indicates that the RESTCONF
       client supports initiating HTTPS connections to RESTCONF
       servers. This feature exists as HTTPS might not be a
       mandatory to implement transport in the future.";
    reference
      "RFC 8040: RESTCONF Protocol";
  }

  feature http-listen {
    description
      "The 'http-listen' feature indicates that the RESTCONF client
       supports opening a port to listen for incoming RESTCONF
       server call-home connections using HTTP.  This feature
       exists as not all RESTCONF clients may support RESTCONF
       call home.";
    reference
      "RFC 8071: NETCONF Call Home and RESTCONF Call Home";
  }

  feature https-listen {
    description
      "The 'https-listen' feature indicates that the RESTCONF client
       supports opening a port to listen for incoming RESTCONF
       server call-home connections using HTTPS.  This feature
       exists as not all RESTCONF clients may support RESTCONF
       call home.";
    reference
      "RFC 8071: NETCONF Call Home and RESTCONF Call Home";
  }

  feature central-restconf-client-supported {
   description
      "The 'central-restconf-client-supported' feature indicates
       that the server that implements this module supports
       the top-level 'restconf-client' node.

       This feature is needed as some servers may want to use
       features defined in this module, which requires this
       module to be implemented, without having to support
       the top-level 'restconf-client' node.";
  }

  // Groupings

  grouping restconf-client-initiate-stack-grouping {
    description
      "A reusable grouping for configuring a RESTCONF client
       'initiate' protocol stack for a single outbound connection.";
    container http-client-parameters {
      description
        "HTTP-level client parameters to listen
         for RESTCONF over HTTPS connections.";
      uses httpc:http-client-grouping;
    }
  } // restconf-client-initiate-stack-grouping

  grouping restconf-client-listen-stack-grouping {
    description
      "A reusable grouping for configuring a RESTCONF client
       'listen' protocol stack for listening on a single port.  The
       'listen' stack supports call home connections, as
       described in RFC 8071";
    reference
      "RFC 8071: NETCONF Call Home and RESTCONF Call Home";
    choice transport {
      mandatory true;
      description
        "Selects between available transports.";
      case http {
        if-feature "http-listen";
        container http {
          description
            "TCP, HTTP, and RESTCONF configuration to
             listen for RESTCONF over HTTPS connections.

             This transport option is made available to support
             deployments where the TLS connections are terminated
             by another system (e.g., a load balancer) fronting
             the client.";
          container tcp-server-parameters {
            description
              "TCP-level server parameters to listen for
               RESTCONF over HTTP connections.";
            uses tcps:tcp-server-grouping {
              refine "local-bind/local-port" {
                default "4336";
                description
                  "The RESTCONF client will listen on the IANA-
                   assigned well-known port for 'restconf-ch-tls'
                   (4336) if no value is specified.";
              }
            }
          }
          container http-client-parameters {
            description
              "HTTP-level client parameters to listen for
               RESTCONF over HTTP connections.";
            uses httpc:http-client-grouping;
          }
        }
      }
      case https {
        if-feature "https-listen";
        container https {
          description
            "TCP, TLS, HTTP, and RESTCONF configuration to
             listen for RESTCONF over HTTPS connections.";
          container tcp-server-parameters {
            description
              "TCP-level server parameters to listen
               for RESTCONF over HTTPS connections.";
            uses tcps:tcp-server-grouping {
              refine "local-bind/local-port" {
                default "4336";
                description
                  "The RESTCONF client will listen on the IANA-
                   assigned well-known port for 'restconf-ch-tls'
                   (4336) if no value is specified.";
              }
            }
          }
          container http-client-parameters {
            description
              "HTTP-level client parameters to listen
               for RESTCONF over HTTPS connections.";
            uses httpc:http-client-grouping;
          }
        }
      }
    }
  } // restconf-client-listen-stack-grouping

  grouping restconf-client-app-grouping {
    description
      "A reusable grouping for configuring a RESTCONF client
       application that supports both 'initiate' and 'listen'
       protocol stacks for a multiplicity of connections.";
    container initiate {
      if-feature "https-initiate";
      presence
        "Indicates that client-initiated connections have been
         configured.  This statement is present so the mandatory
         descendant nodes do not imply that this node must be
         configured.";
      description
        "Configures client initiating underlying TCP connections.";
      list restconf-server {
        key "name";
        min-elements 1;
        description
          "List of RESTCONF servers the RESTCONF client is to
           maintain simultaneous connections with.";
        leaf name {
          type string;
          description
            "An arbitrary name for the RESTCONF server.";
        }
        container endpoints {
          description
            "Container for a list of endpoints.";
          list endpoint {
            key "name";
            min-elements 1;
            ordered-by user;
            description
              "A non-empty user-ordered list of endpoints for this
               RESTCONF client to try to connect to in sequence.
               Defining more than one enables high-availability.";
            leaf name {
              type string;
              description
                "An arbitrary name for this endpoint.";
            }
            uses restconf-client-initiate-stack-grouping;
          }
        }
        container connection-type {
          description
            "Indicates the RESTCONF client's preference for how
             the RESTCONF connection is maintained.";
          choice connection-type {
            mandatory true;
            description
              "Selects between available connection types.";
            case persistent-connection {
              container persistent {
                presence
                  "Indicates that a persistent connection is to be
                   maintained.";
                description
                  "Maintain a persistent connection to the
                   RESTCONF server. If the connection goes down,
                   immediately start trying to reconnect to the
                   RESTCONF server, using the reconnection strategy.

                   This connection type minimizes any RESTCONF server
                   to RESTCONF client data-transfer delay, albeit
                   at the expense of holding resources longer.";
              }
            }
            case periodic-connection {
              container periodic {
                presence
                  "Indicates that a periodic connection is to be
                   maintained.";
                description
                  "Periodically connect to the RESTCONF server.

                   This connection type decreases resource
                   utilization, albeit with increased delay
                   in RESTCONF server to RESTCONF client
                   interactions.

                   The RESTCONF client SHOULD gracefully close
                   the underlying TLS connection upon completing
                   planned activities.

                   Connections are established at the same start
                   time regardless how long the previous connection
                   stayed open.

                   In the case that the previous connection is
                   still active, establishing a new connection
                   is NOT RECOMMENDED.";
                leaf period {
                  type uint16;
                  units "minutes";
                  default "60";
                  description
                    "Duration of time between periodic
                     connections.";
                }
                leaf anchor-time {
                  type yang:date-and-time {
                    // constrained to minute-level granularity
                    pattern '[0-9]{4}-(1[0-2]|0[1-9])-(0[1-9]|[1-2]'
                          + '[0-9]|3[0-1])T(0[0-9]|1[0-9]|2[0-3]):['
                          + '0-5][0-9]:00(Z|[\+\-]((1[0-3]|0[0-9]):'
                          + '([0-5][0-9])|14:00))?';
                  }
                  description
                    "Designates a timestamp before or after which a
                     series of periodic connections are determined.
                     The periodic connections occur at a whole
                     multiple interval from the anchor time.

                     If an 'anchor-time' is not provided, then the
                     server may implicitly set it to the time when
                     this configuraton is applied (e.g., on boot).

                     For example, for an anchor time is 15 minutes
                     past midnight and a period interval of 24 hours,
                     then a periodic connection will occur 15 minutes
                     past midnight everyday.";
                }
                leaf idle-timeout {
                  type uint16;
                  units "seconds";
                  default "180"; // three minutes
                  description
                    "Specifies the maximum number of seconds
                     that the underlying TCP session may remain
                     idle. A TCP session will be dropped if it
                     is idle for an interval longer than this
                     number of seconds If set to zero, then the
                     RESTCONF client will never drop a session
                     because it is idle.";
                }
              }
            } // periodic-connection
          } // connection-type
        } // connection-type
        container reconnect-strategy {
          description
            "The reconnection strategy directs how a RESTCONF
             client reconnects to a RESTCONF server, after
             discovering its connection to the server has
             dropped, even if due to a reboot.  The RESTCONF
             client starts with the specified endpoint and
             tries to connect to it max-attempts times before
             trying the next endpoint in the list (round
             robin).";
          leaf start-with {
            type enumeration {
              enum first-listed {
                description
                  "Indicates that reconnections should start
                   with the first endpoint listed.";
              }
              enum last-connected {
                description
                  "Indicates that reconnections should start with
                   the endpoint last connected to, if known.  If
                   no previous connection is known, then the
                   first endpoint configured is used.";
              }
              enum random-selection {
                description
                  "Indicates that reconnections should start with
                   a random endpoint.";
              }
            }
            default "first-listed";
            description
              "Specifies which of the RESTCONF server's
               endpoints the RESTCONF client should start
               with when trying to connect to the RESTCONF
               server.";
          }
          leaf max-wait {
            type uint16 {
              range "1..max";
            }
            units "seconds";
            default "5";
            description
              "Specifies the amount of time in seconds after which,
               if the connection is not established, an endpoint
               connection attempt is considered unsuccessful.";
          }
          leaf max-attempts {
            type uint8 {
              range "1..max";
            }
            default "3";
            description
              "Specifies the number times the RESTCONF client
               tries to connect to a specific endpoint before
               moving on to the next endpoint in the list
               (round robin).";
          }
        }
      }
    } // initiate

    container listen {
      if-feature "http-listen or https-listen";
      presence
        "Indicates that client-listening ports have been configured.
         This statement is present so the mandatory descendant nodes
         do not imply that this node must be configured.";
      description
        "Configures the client to accept call-home TCP connections.";
      leaf idle-timeout {
        type uint16;
        units "seconds";
        default "180"; // three minutes
        description
          "Specifies the maximum number of seconds that an
           underlying TCP session may remain idle. A TCP session
           will be dropped if it is idle for an interval longer
           then this number of seconds.  If set to zero, then
           the server will never drop a session because it is
           idle.";
      }
      container endpoints {
        description
          "Container for a list of endpoints.";
        list endpoint {
          key "name";
          min-elements 1;
          description
            "List of endpoints to listen for RESTCONF connections.";
          leaf name {
            type string;
            description
              "An arbitrary name for the RESTCONF listen endpoint.";
          }
          uses restconf-client-listen-stack-grouping;
        }
      }
    } // listen
  } // restconf-client-app-grouping

  // Protocol accessible node for servers that implement this module.
  container restconf-client {
    if-feature central-restconf-client-supported;
    uses restconf-client-app-grouping;
    description
      "Top-level container for RESTCONF client configuration.";
  }
}
