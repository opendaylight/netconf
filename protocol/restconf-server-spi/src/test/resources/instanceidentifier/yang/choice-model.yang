module choice-model {
  namespace "choice:ns";
  prefix choice-model;

  container cont-root {
    container cont1 {
      choice choice1 {
        case case1 {
          container case-cont1 {
            leaf case-leaf1 {
              type string;
            }
          }
        }
      }
    }
  }
}
