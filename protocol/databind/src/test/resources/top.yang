module top {
  namespace "http://example.com/schema/1.2/config";
  prefix top;

  revision 2025-03-31 {
    description "Test revision";
  }

  container top {
    choice choice {
      case a {
        container cont {
          leaf data {
            type string;
          }
        }
      }
      case b {
        list entry-list {
          container entry {
            leaf id {
              type uint32;
            }
          }
        }
      }
    }

    list interfaces {
      container interface {
        leaf name {
          type string;
        }
      }
    }

    list users {
      container user {
        leaf name {
          type string;
        }
        container company-info {
          leaf id {
            type int32;
          }
          leaf dept {
            type string;
          }
        }
        leaf type {
          type string;
        }
        leaf id {
          type int32;
        }
      }
    }
  }

  notification topNotif {
    description
      "This notification is sent to signal the end of a replay
      portion of a subscription.";
    container noti-cont {
      leaf noti-leaf {
        type string;
      }
    }

    list noti-list {
      leaf list-leaf {
        type string;
      }
    }
  }
}
