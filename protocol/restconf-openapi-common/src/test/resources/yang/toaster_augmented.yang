module toaster-augmented {

    yang-version 1;

    namespace
      "http://netconfcentral.org/ns/toaster/augmented";

    prefix toast;
    import toaster2 {prefix tst; revision-date 2009-11-20;}

    revision "2014-07-14" {
    }

    augment "/tst:toaster/tst:toasterSlot" {
        container slotInfo {
            leaf numberOfToastPrepared {
                type uint32;
            }
        }
    }
}
