module strings-from-regex {
  yang-version 1.1;
  namespace "urn:ietf:params:xml:ns:yang:strings:regex";
  prefix "str-rx";

  typedef MacAddress {
    type string {
    pattern '[0-9a-fA-F]{2}(:[0-9a-fA-F]{2}){5}';
    }
  }

  typedef Date-Time {
    type string {
      pattern '\d{4}-\d{2}-\d{2}T\d{2}:\d{2}:\d{2}(\.\d+)?(Z|[\+\-]\d{2}:\d{2})';
    }
  }

  typedef ipv4-address {
    type string {
      pattern '(([0-9]|[1-9][0-9]|1[0-9][0-9]|2[0-4][0-9]|25[0-5])\.){3}'
        + '([0-9]|[1-9][0-9]|1[0-9][0-9]|2[0-4][0-9]|25[0-5])(%[\p{N}\p{L}]+)?';
    }
  }

  container test {
    leaf mac-address {
      type MacAddress;
    }
    leaf login-date-time {
      type Date-Time;
    }
    leaf ipv4-address {
      type ipv4-address;
    }
  }
}
