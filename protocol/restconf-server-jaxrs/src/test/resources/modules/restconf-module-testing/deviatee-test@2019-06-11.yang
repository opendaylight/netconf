module deviatee-test {
  yang-version 1.1;
  namespace "http://tech/pantheon/deviatee-test";
  prefix dev;

  organization
        "PANTHEON.tech s.r.o.";

  description
    "Prepared to receive deviations";

  revision 2019-06-11 {
    description
      "Deviation test";
  }

  container test-container {
    leaf comment {
      type string {
        length "0 .. 60";
    }
    description
     "Just for Deviation testing";
    }
  }
}
