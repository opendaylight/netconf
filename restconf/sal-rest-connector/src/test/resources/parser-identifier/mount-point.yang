module mount-point {
  namespace "mount:point";
  prefix "mountp";
  yang-version 1;

  import parser-identifier-included { prefix pii; revision-date 2016-06-02; }

  revision 2016-06-02 {
    description "Initial revision.";
  }

  container mount-container {
    list point {
      uses pii:group1;
    }

    leaf point-number {
      type uint8;
    }
  }
}
