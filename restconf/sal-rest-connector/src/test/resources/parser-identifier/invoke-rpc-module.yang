module invoke-rpc-module {
  namespace "invoke:rpc:module";
  prefix "inrpcmod";
  yang-version 1;

  revision 2017-23-05 {
      description "Initial revision.";
  }

  rpc rpc-test {
      input {
          container cont {
              leaf lf {
                  type string;
              }
          }
      }
      output {
          container cont-out {
              leaf lf-out {
                  type string;
              }
          }
      }
  }
}
