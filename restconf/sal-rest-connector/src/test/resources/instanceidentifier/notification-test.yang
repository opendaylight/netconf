module notification-test {
    namespace "notifi:test";
    prefix nott;

    import system-connector{
        prefix sys;
        revision-date 2016-05-10;
    }

    revision "2016-09-27" {
        description
                "Initial revision.";
    }

    notification notifi{
        uses sys:connectors;
    }
}
