module odl-rest-connector {
    yang-version 1;
    namespace "urn:opendaylight:params:xml:ns:yang:rest:connector";
    prefix "rest-connector";

    import config { prefix config; revision-date 2013-04-05; }
    import opendaylight-md-sal-dom {prefix dom; revision-date 2013-10-28;}
    import opendaylight-md-sal-binding {prefix sal; revision-date 2013-10-28;}
    import ietf-inet-types {prefix inet; revision-date 2010-09-24;}
 
    description
        "Service definition for Rest Connector";
 
    revision "2016-03-16" {
        description
            "Initial revision";
    }
    
    identity rest-connector {
        base "config:service-type";
        config:java-class "org.opendaylight.restconf.rest.api.connector.RestConnector";
    }
    
    identity rest-connector-provider {
        base config:module-type;
        config:provided-service rest-connector;
        config:java-name-prefix RestConnector;
    }

    augment "/config:modules/config:module/config:configuration" {
        case rest-connector-impl {
            when "/config:modules/config:module/config:type = 'rest-connector-provider'";
            leaf websocket-port {
                mandatory true;
                type inet:port-number;
            }
            container dom-broker {
                uses config:service-ref {
                    refine type {
                        mandatory true;
                        config:required-identity dom:dom-broker-osgi-registry;
                    }
                }
            }
        }
    }
}
