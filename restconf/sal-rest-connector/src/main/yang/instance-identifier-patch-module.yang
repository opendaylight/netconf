module instance-identifier-patch-module {
  namespace "instance:identifier:patch:module";

  prefix "iipmodule";
  revision 2015-11-21 {
  }


  container bgp-linkstate-app-config {
      leaf iana-linkstate-attribute-type {
          description "If true (default) linkstate attribute type (=29) allocated by IANA is used,
                       else type (=99) is used for parsing/serialization";
          type boolean;
          default true;
      }
  }

  container patch-cont {
    container patch-cont2 {
        leaf cont-leaf {
            type string;
        }
    }

    list my-list1 {

        description "PATCH /restconf/config/instance-identifier-patch-module:patch-cont/my-list1/leaf1";

        key name;

        leaf name {
            type string;
        }

        leaf my-leaf11 {
            type string;
        }

        leaf my-leaf12 {
            type string;
        }

        list my-list2 {
            key name;

            leaf name {
                type string;
            }

            leaf my-leaf21 {
                type string;
            }

            leaf my-leaf22 {
                type string;
            }
        }
    }
  }
}
