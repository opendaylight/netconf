module identityref-module {
  namespace "identityref:module";  

  prefix "iderefmod";
  
  import identity-module {prefix idemo; revision-date 2013-12-02; }
   
  revision 2013-12-02 {    
  }
  
	container cont {
	   container cont1 {
    		leaf lf1 {
    			type identityref {
    				base "idemo:iden";
    			}
    		}
		}
	}
	  
}
