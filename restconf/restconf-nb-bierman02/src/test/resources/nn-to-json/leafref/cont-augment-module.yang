module cont-augment-module {
  namespace "cont:augment:module";

  prefix "cntaugmod";

  import main-module {prefix mamo; revision-date 2013-12-02;}

  revision 2013-12-02 {

  }

  augment "/mamo:cont" {
  	leaf-list lflst1 {
  		type leafref {
  			path "../mamo:lf1";
  		}
  	}

  	leaf lf4 {
  		type leafref {
  			path "../mamo:lf1";
  		}
  	}

  	/* reference to not leaf element */
  	leaf lf6 {
  		type leafref {
  			path "../lflst1";
  		}
  	}

  	leaf lf7 {
  		type leafref {
  			path "../lf4";
  		}
  	}
  }
  
}
