module simple-nodes {
    yang-version 1;
    namespace "urn:opendaylight:simple-nodes";
    prefix "sn";

    description
        "test file containing yang data nodes";   

    revision "2013-07-30" {
        description
            "Initial revision.";
        reference "will be defined";
    }
    
    container users {
        leaf user {
            type string;
        }
        
        leaf group {
            type string;
        }
    }

    list user {
         key "name class";
         leaf name {
             type string;
         }
         leaf full-name {
             type string;
         }
         leaf class {
             type string;
         }
    }
    
    list userWithoutClass {
        key "name";
        leaf name {
            type string;
        }
        leaf full-name {
            type string;
        }
        container inner-container {
            leaf inner-list {
                type uint16;
            }
        }
    }
    
     container food {
       choice snack {
           case sports-arena {
               leaf pretzel {
                   type string;
               }
               leaf beer {
                   type string;
               }
               container nonalcoholic {
                   leaf beer {
                       type string;
                   }
               }
           }
           case late-night {
               leaf chocolate {
                   type enumeration {
                       enum dark;
                       enum milk;
                       enum first-available;
                   }
               }
           }
       }
    }
    
}
