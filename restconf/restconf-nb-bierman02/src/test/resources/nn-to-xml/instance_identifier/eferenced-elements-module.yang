module referenced-elements-module {
  namespace "referenced:elements:module";  

  prefix "refelmo";
   
  revision 2013-12-03 {    
  }
  
	container cont {
		leaf lf1 {
			type string;				
			}
		}
		leaf-list lflst1 {
			type uint32;
		}
		
	}
	  
}
