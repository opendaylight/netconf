module invoke-rpc-module {
  namespace "invoke:rpc:module";  

  prefix "inrpcmod";
  	  
  revision 2013-12-03 {
  
  }

  rpc rpc-test {
      input {
          container cont {
              leaf lf {
                  type string;
              }
          }
      }
      output {
          container cont-out {
              leaf lf-out {
                  type string;
              }
          }
      }
  }  

  rpc rpc-noop {
  }

}
