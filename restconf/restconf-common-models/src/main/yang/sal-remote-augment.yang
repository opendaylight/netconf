module sal-remote-augment {
  namespace "urn:sal:restconf:event:subscription";
  prefix "odl-sar";

  import sal-remote { prefix rmt; }

  description
    "Set of augmentations defining more granular control over the scope of created streams.";

  revision 2023-11-03 {
    description
      "Revised version with the following changes:
       - datastore parameter is documented to default to CONFIGURATION
       - scope parameter to create-data-change-event-subscription is obsolete
       - notification-output-type parameter is obsolete";
  }

  revision 2014-07-08 {
    description "Initial revision";
  }

  grouping notification-output-type-grouping {
    leaf notification-output-type {
      status obsolete;
      description "Input parameter which type of output will be parsed on notification";
      type enumeration {
        enum JSON;
        enum XML;
      }
      default XML;
    }
  }

  augment "/rmt:create-data-change-event-subscription/rmt:input" {
    leaf datastore {
      type enumeration {
        enum OPERATIONAL;
        enum CONFIGURATION;
      }
      default CONFIGURATION;
    }

    leaf scope {
      status obsolete;
      type enumeration {
        enum BASE;
        enum ONE;
        enum SUBTREE;
      }
    }

    uses notification-output-type-grouping;
  }

  augment "/rmt:create-notification-stream/rmt:input" {
    uses notification-output-type-grouping;
  }
}
