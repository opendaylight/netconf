module test-container-childs {
  namespace "http://example.com/test/container/child";
  prefix "tcc";
  revision 2023-09-28;

  container root-container {
    container nested-container {
      list mandatory-list {
        min-elements 2;
        key id;
        leaf id {
          type uint32;
        }
        leaf name {
          type string;
        }
      }
    }
  }
}
