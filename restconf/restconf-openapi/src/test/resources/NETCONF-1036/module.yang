module module {
  yang-version 1.1;
  namespace "urn:ietf:params:xml:ns:yang:test:module";
  prefix "mod";
  grouping simple {
    container simple-root {
      leaf leaf-a {
        type string;
      }
      leaf leaf-b {
        type string;
      }
    }
  }

  grouping lists {
    list top-list {
      key "key-1 key-2";

      leaf key-1 {
        type string;
      }
      leaf key-2 {
        type string;
      }
    }
  }

  container root {
    uses simple;
    uses lists;
  }
}
