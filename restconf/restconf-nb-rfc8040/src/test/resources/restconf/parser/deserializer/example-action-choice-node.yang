module example-action-choice-node {
  yang-version 1.1;
  namespace "https://example.com/ns/example-action-choice-node";
  prefix "act";

  organization "Example, Inc.";
  contact "support at example.com";
  description "Example Actions Data Model Module.";

  revision "2019-11-11" {
     description "Initial version.";
     reference "example.com document 2-9973.";
  }

  container interfaces {
    choice interface-type {
      container typeA-gigabyte {
        list interface {
          key name;
          description "One interface entry.";
          leaf name {
            type string;
            description "Interface name.";
          }

          action reboot {
            description "Reboot operation.";
            input {
              leaf delay {
                type uint32;
                units "seconds";
                description  "Number of seconds to wait before initiating the reboot operation.";
              }
              leaf message {
                type string;
                description  "Log message to display when reboot is started.";
              }
            }
          }
        }
      }
    }
  }
}
