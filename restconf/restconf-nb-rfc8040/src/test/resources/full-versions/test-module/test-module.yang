module test-module {
  namespace "test:module";
  prefix tstmod;

  revision 2014-01-09 {
  }

  identity module-type {
  }

  identity test-identity {
  }

  container interfaces {
    container class {
        leaf name {
            type string;
        }
        leaf address {
            type string;
        }
        leaf email {
            type string;
        }
    }
  }

  container cont {
    container cont1 {
        leaf lf11 {
            type string;
        }
        leaf lf12 {
            type string;
        }
    }
    list lst1 {
        key "lf11";
        leaf lf11 {
            type string;
        }
    }
  }

  container modules {
      list module {
          key "type name";
          leaf name {
              type string;
              mandatory true;
          }

          leaf type {
              type identityref {
                  base module-type;
              }
              mandatory true;
          }

          leaf data {
              type string;
          }
      }
  }

  list lst-with-composite-key {
    key "key1 key2";
    leaf key1 {
        type string;
    }
    leaf key2 {
        type uint8;
    }
  }

  rpc no-payload-rpc-test {
      output {
          container cont-output {
          }
      }
  }

  rpc rpc-test {
    input {
      container cont {
        container cont1 {
            leaf lf11 {
                type string;
            }
            leaf lf12 {
                type string;
            }
        }
      }
    }
    output {
        container cont-output {
        }
    }
  }
}
