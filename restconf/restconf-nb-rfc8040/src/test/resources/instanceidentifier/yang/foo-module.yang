module foo-module {
  namespace "foo:module";

  prefix "foo-module";
    revision 2016-09-29 {
  }

  /* This container has the same name as container in bar-module */
  container foo-bar-container {
  }
}
