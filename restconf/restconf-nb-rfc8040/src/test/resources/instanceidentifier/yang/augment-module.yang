module augment-module {
  namespace "augment:module";

  prefix "amodule";

  import instance-identifier-module {prefix imodule; revision-date 2014-01-17;}

  revision 2014-01-17 {
  }

  augment "/imodule:cont/imodule:cont1" {
   list lst11 {
       key "keyvalue111 keyvalue112";
       leaf keyvalue111 {
           type string;
       }
       leaf keyvalue112 {
           type string;
       }
    }
  }

    augment "/imodule:cont" {
      container cont-augment {
            leaf leaf1 {
                type string;
            }
        }
    }

    augment "/imodule:cont" {
        choice augment-choice1 {
            case case1 {
                container case-container1 {
                    leaf case-leaf1 {
                        type string;
                    }
                }
            }

            case case2 {
                container case-container2 {
                    leaf case-leaf2 {
                        type string;
                    }
                }
            }
        }
    }

    augment "/imodule:cont/augment-choice1/case1" {
        choice augment-choice2 {
            case case11 {
                container case-choice-case-container1 {
                    leaf case-choice-case-leaf1 {
                        type string;
                    }
                }
            }
        }
    }

}
