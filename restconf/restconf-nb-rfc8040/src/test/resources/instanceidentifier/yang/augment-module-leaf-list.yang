module augment-module-leaf-list {
  namespace "augment:module:leaf:list";

  prefix "amodulelflst";

  import instance-identifier-module {prefix imodule; revision-date 2014-01-17;}

  revision 2014-01-27 {
  }

    augment "/imodule:cont/imodule:cont1" {
       leaf-list lflst11 {
           type string;
       }
       leaf lf11 {
            type instance-identifier;
       }
    }
}
