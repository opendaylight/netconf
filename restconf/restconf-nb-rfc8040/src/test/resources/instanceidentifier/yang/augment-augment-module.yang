module augment-augment-module {
  namespace "augment:augment:module";

  prefix "aamodule";

  import augment-module {prefix amodule; revision-date 2014-01-17;}
  import instance-identifier-module {prefix imodule; revision-date 2014-01-17;}

  revision 2014-01-17 {
  }

  augment "/imodule:cont/imodule:cont1/amodule:lst11" {
        leaf lf111 {
            type instance-identifier;
        }
        leaf lf112 {
            type string;
        }
  }
}
