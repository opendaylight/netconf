module path-params-test {
  yang-version 1.1;
  namespace "urn:ietf:params:xml:ns:yang:test:params";
  prefix "pt";

  container cont {
    list list1 {
      key name;
      leaf name {
        type string;
      }
      list list2 {
        key name;
        leaf name {
          type string;
        }
      }
    }
    list list3 {
      key name;
      leaf name {
        type string;
      }
    }
  }
}
