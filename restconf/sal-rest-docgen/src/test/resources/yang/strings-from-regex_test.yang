module strings-from-regex_test {
  yang-version 1;
  namespace "urn:ietf:params:xml:ns:yang:test:strings:regex";
  prefix "str-rx";

  typedef PhysAddress {
    type string {
      pattern "((([0-9A-Fa-f]{2}){1}):)";
    }
  }

  typedef MacAddress {
    type string {
    length "6";
    pattern "((([0-9A-Fa-f]{2}){1}):)";
    }
  }

  typedef Time {
    type string {
      pattern "(?:\d{4}-\d{2}-\d{2}T\d{2}:\d{2}:\d{2}(\.\d+)?(Z|[\+\-]\d{2}:\d{2}))";
    }
  }

  typedef Revision {
    type string {
    pattern "(?:\d{4}-\d{2}-\d{2})";
    }
  }

  container test {
    leaf phys-address {
      type PhysAddress;
    }
    leaf mac-address {
      type MacAddress;
    }
    leaf revisions {
      type Revision;
    }
    leaf login-time {
      type Time;
    }
  }
}
