module list-test {
  namespace "urn:opendaylight:params:xml:ns:yang:netconf:monitoring:list-test";
  prefix "ltest";
  revision 2023-07-31 {
    description "Test model.";
  }
  container cont {
    list list1 {
      key "key1";
      leaf key1 {
        type string;
      }
      leaf value1 {
        type string;
      }
    }
    list list2 {
      key "key2";
      leaf key2 {
        type string;
      }
      leaf value2 {
        type string;
      }
      list list3 {
        key "key3";
        leaf key3 {
          type string;
        }
        leaf value3 {
          type string;
        }
      }
    }
  }
}
