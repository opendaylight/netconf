module deserializer-test-included {
  namespace "deserializer:test:included";
  prefix "dti";
  yang-version 1;

  revision 2016-06-06 {
    description
      "Initial revision.";
  }

  identity root-identity {
    description "Test root identity.";
  }

  list augmented-list {
    key list-key;

    leaf list-key {
      type uint16;
    }

    leaf list-value {
      type string;
    }
  }

  container refs {
    list list-with-identityref {
      key "id";

      leaf id {
        type leafref {
          path "../../ref";
        }
      }

      leaf foo {
        type empty;
      }
    }

    leaf ref {
      type identityref {
        base "root-identity";
      }
    }
  }
}
